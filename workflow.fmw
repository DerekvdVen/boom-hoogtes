FME workspace workflow.fmw

Parameters:
- anaconda_loc = C:\Users\Derek\Anaconda3   # Where is anaconda3 stored?
- polygon_file_location = data/geodatabase/OMS_NHM_20201223.gdb   # Select shapefile in data/polygon_input/
- identifier_column_name = KRCode   # What is the ID column name of the shapefile?
- lcheck_factor = 0.3   # OPTIONAL, hoe strict checken?
- squareness_factor = 0.7   # OPTIONAL, hoe snel zijn polygonen vierkant?
- lf_factor = 2.5   # OPTIONAL, welke hoogte/breedte verhouding telt als langwerpig?
- cl_distance = 1.0   # OPTIONAL, simplification for centerline calculation
- layer = vWaterafvoer   # Welke laag wil je inladen?
- anaconda_location = C:\Users\Derek\Anaconda3   # where is anaconda?

Creator
    GEOMTYPE = Geometry Object
    NUM = 1
    CREATED -> SystemCaller
Note: .\workflow.bat $(anaconda_loc) $(polygon_file_location) $(identifier_column_name)
Note: runs workflow.bat
Note: output in output/output.xlsx
SystemCaller
    ATTR = _exit_code
    CMD = .\workflow.bat $(anaconda_location)
